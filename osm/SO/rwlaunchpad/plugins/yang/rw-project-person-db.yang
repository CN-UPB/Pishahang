/*
 *
 *   Copyright 2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */


module rw-project-person-db
{
  namespace "http://riftio.com/ns/riftware-1.0/rw-project-person-db";
  prefix "rw-project-person-db";

  import rw-project {
    prefix "rw-project";
  }

  revision 2016-04-03 {
    description
      "Initial revision.
      Test YANG for unit testing.";
  }

  augment "/rw-project:project" {
    container person {
      
      leaf name {
        description
          "This is the person's name.";
        type string;
      }
    }

    container flat-person {
      leaf name {
        type string;
      }
    }
  }
}
