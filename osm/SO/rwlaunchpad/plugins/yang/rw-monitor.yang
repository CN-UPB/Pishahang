/*
 * 
 *   Copyright 2016 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 */



/**
 * @file rw-monitor.yang
 * @author Joshua Downer
 * @date 2015/10/30
 * @brief NFVI Monitor
 */

module rw-monitor
{
  namespace "http://riftio.com/ns/riftware-1.0/rw-monitor";
  prefix "rw-monitor";

  import rw-cli-ext {
    prefix "rwcli";
  }

  import rw-yang-types {
    prefix "rwt";
  }

  import rw-cloud {
    prefix "rw-cloud";
  }

  import rw-nsr {
    prefix "rw-nsr";
  }

  import rw-vnfr {
    prefix "rw-vnfr";
  }

  import rwcal {
    prefix "rwcal";
  }

  import ietf-yang-types {
    prefix "yang";
  }

  import rw-project-mano {
    prefix "rw-project-mano";
  }

  revision 2015-10-30 {
    description
      "Initial revision.";
  }
}
