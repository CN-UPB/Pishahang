/*
 * 
 *   Copyright 2016 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 */



/**
 * @file rw-vnfm.yang
 * @author Rajesh Velandy
 * @date 2015/10/07
 * @brief VNFM  yang
 */

module rw-vnfm
{
  namespace "http://riftio.com/ns/riftware-1.0/rw-vnfm";
  prefix "rw-vnfm";

  import vld {
    prefix "vld";
  }

  import vlr {
    prefix "vlr";
  }

  import rw-vlr {
    prefix "rw-vlr";
  }

  import rw-vns {
    prefix "rw-vns";
  }

  import rw-project-vnfd {
    prefix "rw-project-vnfd";
  }

  import rw-vnfr {
    prefix "rw-vnfr";
  }

  import rw-yang-types {
    prefix "rwt";
  }

  import rw-manifest {
    prefix "rw-manifest";
  }

  import rw-resource-mgr {
    prefix "rw-resource-mgr";
  }

  import rw-launchpad {
    prefix "rw-launchpad";
  }

  import rw-project-mano {
    prefix "rw-project-mano";
  }

  revision 2015-10-07 {
    description
      "Initial revision.";
  }
}
