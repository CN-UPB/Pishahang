/*
 * 
 *   Copyright 2016-2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-vnfd-base
{
  namespace "http://riftio.com/ns/riftware-1.0/rw-vnfd-base";
  prefix "rw-vnfd-base";

  import vnfd {
    prefix "vnfd";
  }

  import rwvcs-types {
    prefix "rwvcstypes";
  }

  import ietf-yang-types {
    prefix "yang";
  }

  import mano-types {
    prefix "manotypes";
  }

  revision 2017-02-28 {
    description
      "Initial revision. This YANG file defines
       common structs for extending MANO VNFD";
    reference
      "Derived from earlier versions of base YANG files";
  }

  grouping rw-vnfd-ext {
    leaf meta {
      description
        "Any meta-data needed by the UI";
      type string;
    }

  }
  grouping ssh-key {
    leaf ssh-key {
      description
        "Whether SSH keys need to be generated and passed
         to the RO and VCA during instantiation.";
      type boolean;
    }
  }
}
// vim: sw=2
