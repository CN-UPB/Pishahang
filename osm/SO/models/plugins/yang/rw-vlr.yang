/*
 * 
 *   Copyright 2016-2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-vlr
{
  namespace "http://riftio.com/ns/riftware-1.0/rw-vlr";
  prefix "rw-vlr";

  import mano-types {
    prefix "manotypes";
  }

  import ietf-inet-types {
    prefix "inet";
  }

  import vlr {
    prefix "vlr";
  }

  import vnfd-base {
    prefix "vnfd-base";
  }

  import rw-cloud {
    prefix "rw-cloud";
  }

  import ietf-yang-types {
    prefix "yang";
  }

  import rw-project {
    prefix "rw-project";
  }

  revision 2017-02-08 {
    description
      "Update model to support projects.";
  }

  revision 2015-09-30 {
    description
      "Initial revision. This YANG file augments
       the base MANO VNFD";
    reference
      "Derived from earlier versions of base YANG files";
  }

  augment /rw-project:project/vlr:vlr-catalog/vlr:vlr {

    leaf datacenter {
      description
          "Datacenter name to use when instantiating
          the network service.";
      type string;
    }


    leaf network_pool {
      description "The network pool the resource was allocated from.";
      type string;
    }

    leaf assigned-subnet {
      description "Subnet added for the VL";
      type string;
    }

    leaf operational-status-details {
      description
        "The error message in case of a failed VLR operational status";
      type string;
    }

    list virtual-connection-points {
      key name;
      uses vnfd-base:common-connection-point;

      leaf-list associated-cps {
        type string;
      }

      leaf connection-point-id {
        description "VIM identifier for connection point";
        type string;
      }
      
      leaf ip-address {
        description "IP Address of virtual connection point";
        type inet:ip-address;
      }
      leaf mac-address {
        description "MAC Address of the virtual connection point";
        type string;
      }
    }
  }
}

// vim: sw=2
