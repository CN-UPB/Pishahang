/*
 * 
 *   Copyright 2016-2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-nsd-base
{
  namespace "http://riftio.com/ns/riftware-1.0/rw-nsd-base";
  prefix "rw-nsd-base";

  import mano-types {
    prefix "manotypes";
  }

  revision 2017-02-28 {
    description
      "Initial revision. This YANG file defines
       grouping to extend the base MANO NSD";
    reference
      "Derived from earlier versions of base YANG files";
  }

  grouping rw-nsd-ext {
    uses manotypes:control-param;
    uses manotypes:action-param;
    leaf meta {
      description
        "Any meta-data needed by the UI";
      type string;
    }
  }
}

// vim: sw=2
