/*
 * 
 *   Copyright 2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-ro-account-annotation
{
  namespace "http://riftio.com/ns/riftware-1.0/rw-ro-account-annotation";
  prefix "rw-ro-account-ann";

  import rw-ro-account {
    prefix rw-ro-account;
  }

  import rw-project {
    prefix "rw-project";
  }

  import tailf-common {
    prefix tailf-common;
  }

  tailf-common:annotate "/rw-project:project/rw-ro-account:ro-account-state" {
    tailf-common:callpoint rw_callpoint;
  }

  tailf-common:annotate "/rw-project:project/rw-ro-account:ro-account-state/rw-ro-account:account/rw-ro-account:connection-status" {
    tailf-common:callpoint rw_callpoint;
  }

  tailf-common:annotate "/rw-project:project/rw-ro-account:ro-account-state/rw-ro-account:account/rw-ro-account:instance-ref-count" {
    tailf-common:callpoint rw_callpoint;
  }

  tailf-common:annotate "/rw-project:project/rw-ro-account:ro-account-state/rw-ro-account:account/rw-ro-account:datacenters" {
    tailf-common:callpoint rw_callpoint;
  }

  tailf-common:annotate "/rw-project:project/rw-ro-account:ro-account-state/rw-ro-account:account/rw-ro-account:config-data" {
    tailf-common:callpoint rw_callpoint;
  }

  tailf-common:annotate "/rw-ro-account:update-ro-account-status" {
    tailf-common:actionpoint rw_actionpoint;
  }
}
