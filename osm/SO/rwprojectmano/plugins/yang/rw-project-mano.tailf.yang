/*
 *
 *   Copyright 2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 */

module rw-project-mano-tailf
{
  namespace "http://riftio.com/ns/riftware-1.0/rw-project-mano-tailf";
  prefix "rw-project-mano-tailf";

  import rw-project {
    prefix "rw-project";
  }

  import tailf-common {
    prefix tailf;
  }

  import rw-project-mano {
    prefix "rw-project-mano";
  }

  revision 2017-04-04 {
    description
      "Initial revision.";
  }

  tailf:annotate "/rw-project:project/rw-project:project-state/rw-project-mano:mano-role" {
    tailf:callpoint rw_callpoint;
  }
}
